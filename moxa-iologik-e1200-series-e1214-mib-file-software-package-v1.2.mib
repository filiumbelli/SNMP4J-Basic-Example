-- *****************************************************************
-- Moxa Active Ethernet I/O Server MIB
--
-- 01-03-2013
--
-- Copyright (c) 2013 by Moxa Automation Co., Ltd.
-- All rights reserved.
-- *****************************************************************

MOXA-IO-E1214-MIB DEFINITIONS ::= BEGIN
    IMPORTS
        enterprises, Unsigned32, Integer32, MODULE-IDENTITY, OBJECT-TYPE, NOTIFICATION-TYPE FROM SNMPv2-SMI;
   
-- 1.3.6.1.4.1.8691.10.1214
    e1214   MODULE-IDENTITY
    LAST-UPDATED "201609061100Z"
    ORGANIZATION "Moxa Automation,Inc."
    CONTACT-INFO
            "Postal: Moxa Automation,Inc.
             Fl.4, No.135,Lane 235,Pao-Chiao Rd.
             Shing Tien City,Taipei,Taiwan,R.O.C
             Tel: +866-2-89191230 "
    DESCRIPTION
            "The MIB module for Moxa ioLogik Remote Ethernet I/O specific information." 

	REVISION "201609061100Z"      
	DESCRIPTION
            "fix typo (doPulsONWidth -> doPulseONWidth, doPulsOFFWidth -> doPulseOFFWidth)"			
		
			
	REVISION "201607281500Z"      
	DESCRIPTION
            "add new item of relay total/current count, reset current count and modfiy counter overflow item"		
			
	REVISION "201603311500Z"      
	DESCRIPTION
            "rename description of each item"
	
	REVISION "201601140900Z"      
	DESCRIPTION
            "remove di/do type entry"  
			
	REVISION "201601041300Z"      
	DESCRIPTION
            "Validate level 3 of simple web"   
	REVISION "201512041600Z"
    DESCRIPTION
            "First version of this MIB."
    REVISION "201302211400Z"    
    DESCRIPTION
            "The Trap Support SNMPv2" 
                        
           ::= { ioLogik 1214 }    -- 1.3.6.1.4.1.8691.10.1214
           
-- 1.3.6.1.4.1.8691
    moxa OBJECT IDENTIFIER ::= { enterprises 8691 }

-- 1.3.6.1.4.1.8691.10
    ioLogik OBJECT IDENTIFIER ::= { moxa 10 }

-- 1.3.6.1.4.1.8691.10.1214.1
    totalChannelNumber OBJECT-TYPE
        SYNTAX Integer32 (1..16)
        MAX-ACCESS read-only
        STATUS current
        DESCRIPTION
            "Total I/O channels."
        ::= { e1214 1 }

-- 1.3.6.1.4.1.8691.10.1214.2
    serverModel OBJECT-TYPE
        SYNTAX OCTET STRING
        MAX-ACCESS read-only
        STATUS current
        DESCRIPTION
            "The I/O server model."
        ::= { e1214 2 }

-- 1.3.6.1.4.1.8691.10.1214.3
    systemTime OBJECT-TYPE
        SYNTAX Integer32
        MAX-ACCESS read-only
        STATUS current
        DESCRIPTION
            "I/O server up time (in seconds)."
        ::= { e1214 3 }

-- 1.3.6.1.4.1.8691.10.1214.4
    firmwareVersion OBJECT-TYPE
        SYNTAX OCTET STRING
        MAX-ACCESS read-only
        STATUS current
        DESCRIPTION
            "The firmware version."
        ::= { e1214 4 }


----------------------------------------------------------------
-- I/O
-- 1.3.6.1.4.1.8691.10.1214.10          
    e1214monitor OBJECT IDENTIFIER ::= { e1214 10 }
----------------------------------------------------------------
-- DI channel
diTable OBJECT-TYPE
        SYNTAX          SEQUENCE OF DIEntry
        MAX-ACCESS      not-accessible
        STATUS          current
        DESCRIPTION     
            "The DI channel monitor table"
        ::= { e1214monitor 1 }

diEntry OBJECT-TYPE
        SYNTAX          DIEntry
        MAX-ACCESS      not-accessible
        STATUS          current
        DESCRIPTION     
            "The DI channel monitor item"
        INDEX { diIndex }
        ::= { diTable 1 }

DIEntry ::= SEQUENCE {
                diIndex     Integer32,
                diMode      Integer32,
                diStatus    Integer32,
                diFilter    Integer32,
                diTrigger   Integer32,
                diCntStart  Integer32,
				diCounterReset Integer32,
				diCounterOverflowFlag Integer32,
				diCounterOverflowFlagClear Integer32				
                 }

diIndex OBJECT-TYPE
        SYNTAX          Integer32  (0..15)
        MAX-ACCESS      read-only
        STATUS          current
        DESCRIPTION     
            "DI - index"
        ::= { diEntry 1 }          
        
diMode OBJECT-TYPE
        SYNTAX          Integer32  (0..1)
        MAX-ACCESS      read-write
        STATUS          current
        DESCRIPTION     "DI - mode (0: DI, 1: Counter mode)"
        ::= { diEntry 3 }
 
diStatus OBJECT-TYPE
        SYNTAX          Integer32 (0..2147483647)
        MAX-ACCESS      read-only
        STATUS          current
        DESCRIPTION     "DI - DI mode status (0: OFF, 1: ON) or Counter mode value"
        ::= { diEntry 4 }
        
diFilter OBJECT-TYPE
        SYNTAX          Integer32  (1..65535)
        MAX-ACCESS      read-write
        STATUS          current
        DESCRIPTION     "DI - filter setting (unit: 1 ms)"
        ::= { diEntry 5 }

diTrigger OBJECT-TYPE
        SYNTAX          Integer32  (0..2)
        MAX-ACCESS      read-write
        STATUS          current
        DESCRIPTION     "DI - Counter mode - event (0: Rising Edge, 1: Falling Edge, 2: Both)"
        ::= { diEntry 6 }

diCntStart OBJECT-TYPE
        SYNTAX          Integer32 (0..1)
        MAX-ACCESS      read-write
        STATUS          current
        DESCRIPTION     "DI - Counter mode - status (0: STOP, 1: START)"
        ::= { diEntry 7 }

diCounterReset OBJECT-TYPE
        SYNTAX          Integer32 (0..1)
        MAX-ACCESS      read-write
        STATUS          current
        DESCRIPTION     "DI - Counter mode - reset to initial value (1: RESET)"
        ::= { diEntry 8 }		
	
diCounterOverflowFlag OBJECT-TYPE
        SYNTAX          Integer32 (0..1)
        MAX-ACCESS      read-only
        STATUS          current
        DESCRIPTION     "DI - Counter mode - overflow flag (0: Normal, 1: Overflow)"
        ::= { diEntry 9 }

diCounterOverflowFlagClear OBJECT-TYPE
        SYNTAX          Integer32 (0..1)
        MAX-ACCESS      read-write
        STATUS          current
        DESCRIPTION     "DI - Counter mode - clear overflow flag (1:CLEAR)"
        ::= { diEntry 10 }			
		
----------------------------------------------------------------
---------------------------------------------------------------- 
-- RELAY channel
doTable OBJECT-TYPE
        SYNTAX          SEQUENCE OF DOEntry
        MAX-ACCESS      not-accessible
        STATUS          current
        DESCRIPTION     
            "The Relay channel monitor table"
        ::= { e1214monitor 2 }

doEntry OBJECT-TYPE
        SYNTAX          DOEntry
        MAX-ACCESS      not-accessible
        STATUS          current
        DESCRIPTION     
            "The Relay channel monitor item"
        INDEX { diIndex }
        ::= { doTable 1 }

DOEntry ::= SEQUENCE {
                    doIndex         Integer32,
                    doMode          Integer32,
                    doStatus        Integer32,
                    doPulseONWidth   Integer32,
                    doPulseOFFWidth  Integer32,
                    doPulseStart    Integer32,
					doTotalCount	Integer32,
					doCurrentCount 	Integer32,
					doCurrentCountReset Integer32
                 }

doIndex OBJECT-TYPE
        SYNTAX          Integer32 (0..15)
		MAX-ACCESS 		read-only
        STATUS          current
        DESCRIPTION     "Relay - index"
        ::= { doEntry 1 }
        
doMode OBJECT-TYPE
        SYNTAX          Integer32 (0..1)
        MAX-ACCESS      read-write
        STATUS          current
        DESCRIPTION     "Relay - mode (0: Relay, 1: Pulse)"
        ::= { doEntry 3 }
        
doStatus OBJECT-TYPE
        SYNTAX          Integer32 (0..1)
        MAX-ACCESS      read-write
        STATUS          current
		DESCRIPTION	"Relay - Relay mode status (0: OFF, 1: ON) or Pulse mode count"
        ::= { doEntry 4 }
        
doPulseONWidth OBJECT-TYPE
        SYNTAX          Integer32 (1..65535)
        MAX-ACCESS      read-write
        STATUS          current
        DESCRIPTION     "Relay - Pulse mode - ON width (unit: 1.5 s)"
        ::= { doEntry 5 }
        
doPulseOFFWidth OBJECT-TYPE
        SYNTAX          Integer32 (1..65535)
        MAX-ACCESS      read-write
        STATUS          current
        DESCRIPTION     "Relay - Pulse mode - OFF width (unit: 1.5 s)"
        ::= { doEntry 6 }

doPulseStart OBJECT-TYPE
        SYNTAX          Integer32 (0..1)
        MAX-ACCESS      read-write
        STATUS          current
        DESCRIPTION     "Relay - Pulse mode - status (0: STOP, 1: START)"
        ::= { doEntry 7 }

doTotalCount OBJECT-TYPE
        SYNTAX          Integer32 (0..2147483647)
        MAX-ACCESS      read-only
        STATUS          current
        DESCRIPTION     "Relay - total count"
        ::= { doEntry 8 }

doCurrentCount OBJECT-TYPE
        SYNTAX          Integer32 (0..2147483647)
        MAX-ACCESS      read-only
        STATUS          current
        DESCRIPTION     "Relay - current count"
        ::= { doEntry 9 }	

doCurrentCountReset OBJECT-TYPE
        SYNTAX          Integer32 (0..1)
        MAX-ACCESS      read-write
        STATUS          current
        DESCRIPTION     "Relay - reset current count (1: RESET)"
        ::= { doEntry 10 }			
                         
----------------------------------------------------------------
---------------------------------------------------------------
-- DI TRAP
-- 1.3.6.1.4.1.8691.10.1214.20
    diTrap OBJECT IDENTIFIER ::= { e1214 20 }

----------------------------------------------------------------
diTrap0 NOTIFICATION-TYPE
		STATUS current
    	DESCRIPTION     "DI-00 - DI mode - status (0: OFF, 1: ON)"
        ::= { diTrap 1 }

diTrap1 NOTIFICATION-TYPE
		STATUS current
    	DESCRIPTION     "DI-01 - DI mode - status (0: OFF, 1: ON)"
        ::= { diTrap 2 }  
        
diTrap2 NOTIFICATION-TYPE
		STATUS current
    	DESCRIPTION     "DI-02 - DI mode - status (0: OFF, 1: ON)"
        ::= { diTrap 3 }

diTrap3 NOTIFICATION-TYPE
		STATUS current
    	DESCRIPTION     "DI-03 - DI mode - status (0: OFF, 1: ON)"
        ::= { diTrap 4 }  
        
diTrap4 NOTIFICATION-TYPE
		STATUS current
    	DESCRIPTION     "DI-04 - DI mode - status (0: OFF, 1: ON)"
        ::= { diTrap 5 }

diTrap5 NOTIFICATION-TYPE
		STATUS current
    	DESCRIPTION     "DI-05 - DI mode - status (0: OFF, 1: ON)"
        ::= { diTrap 6 }


----------------------------------------------------------------
-- DO TRAP
-- 1.3.6.1.4.1.8691.10.1214.21
    doTrap OBJECT IDENTIFIER ::= { e1214 21 }

----------------------------------------------------------------
doTrap0 NOTIFICATION-TYPE
		STATUS current
		DESCRIPTION 	"Relay-00 - Relay mode - status (0: OFF, 1: ON)"
        ::= { doTrap 1 }

doTrap1 NOTIFICATION-TYPE
		STATUS current
		DESCRIPTION 	"Relay-01 - Relay mode - status (0: OFF, 1: ON)"
        ::= { doTrap 2 }

doTrap2 NOTIFICATION-TYPE
		STATUS current
		DESCRIPTION 	"Relay-02 - Relay mode - status (0: OFF, 1: ON)"
        ::= { doTrap 3 }

doTrap3 NOTIFICATION-TYPE
		STATUS current
		DESCRIPTION 	"Relay-03 - Relay mode - status (0: OFF, 1: ON)"
        ::= { doTrap 4 }

doTrap4 NOTIFICATION-TYPE
		STATUS current
		DESCRIPTION 	"Relay-04 - Relay mode - status (0: OFF, 1: ON)"
        ::= { doTrap 5 }

doTrap5 NOTIFICATION-TYPE
		STATUS current
		DESCRIPTION 	"Relay-05 - Relay mode - status (0: OFF, 1: ON)"
        ::= { doTrap 6 }

----------------------------------------------------------------
-- Message TRAP
-- 1.3.6.1.4.1.8691.10.1214.30
	messageTrap OBJECT IDENTIFIER ::= { e1214 30 }

----------------------------------------------------------------
activeMessageTrap NOTIFICATION-TYPE
		STATUS current
		DESCRIPTION 	"The SNMP trap with active message"
        ::= { messageTrap 1 }

END
